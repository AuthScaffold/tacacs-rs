module tacacsrs {
  yang-version 1.1;
  namespace "urn:authscaffold:tacacs-rs:yang:tacacsrs";
  prefix trs;

  import ietf-system {
    prefix sys;
    reference
      "RFC 7317: A YANG Data Model for System Management";
  }

  import ietf-system-tacacs-plus {
    prefix sys-tcs-plus;
    reference
      "RFC 9950: A YANG Data Model for Terminal Access Controller
                 Access-Control System Plus (TACACS+)";
  }

  organization
    "AuthScaffold tacacs-rs project";
  contact
    "Project website: <https://github.com/AuthScaffold/tacacs-rs>";
  description
    "This module contains project-owned TACACS+ configuration
     extensions for tacacs-rs.";

  revision 2026-05-20 {
    description
      "This revision adds configuration for TLS 1.3 PSK psk_dhe_ke
       supported groups.";
    reference
      "RFC 8446: The Transport Layer Security (TLS) Protocol
                 Version 1.3, Sections 4.2.7 and 4.2.8";
  }

  feature psk-dhe-ke-hello-params {
    description
      "TLS 1.3 PSK psk_dhe_ke ClientHello group and key-share
       parameters are configurable.";
  }

  typedef psk-dhe-ke-supported-group {
    type enumeration {
      enum x25519 {
        description
          "This value identifies the X25519 elliptic-curve group.";
        reference
          "RFC 8446: The Transport Layer Security (TLS) Protocol
                     Version 1.3, Section 4.2.7";
      }
      enum secp256r1 {
        description
          "This value identifies the NIST P-256 elliptic-curve group.";
      }
      enum secp384r1 {
        description
          "This value identifies the NIST P-384 elliptic-curve group.";
      }
      enum secp521r1 {
        description
          "This value identifies the NIST P-521 elliptic-curve group.";
      }
      enum ffdhe2048 {
        description
          "This value identifies the ffdhe2048 finite-field
           Diffie-Hellman group.";
        reference
          "RFC 7919: Negotiated Finite Field Diffie-Hellman Ephemeral
                     Parameters for TLS";
      }
      enum ffdhe3072 {
        description
          "This value identifies the ffdhe3072 finite-field
           Diffie-Hellman group.";
      }
      enum ffdhe4096 {
        description
          "This value identifies the ffdhe4096 finite-field
           Diffie-Hellman group.";
      }
      enum ffdhe6144 {
        description
          "This value identifies the ffdhe6144 finite-field
           Diffie-Hellman group.";
      }
      enum ffdhe8192 {
        description
          "This value identifies the ffdhe8192 finite-field
           Diffie-Hellman group.";
      }
    }
    description
      "TLS 1.3 supported groups that tacacs-rs can use to generate a
       psk_dhe_ke ClientHello key share.";
    reference
      "RFC 8446: The Transport Layer Security (TLS) Protocol
                 Version 1.3, Section 4.2.7";
  }

  grouping psk-dhe-ke-hello-params {
    description
      "This grouping contains configuration for TLS 1.3 PSK
       psk_dhe_ke ClientHello supported groups and key shares.";

    leaf-list psk-dhe-ke-groups {
      if-feature "psk-dhe-ke-hello-params";
      type psk-dhe-ke-supported-group;
      ordered-by user;
      description
        "When the client uses TLS 1.3 PSK psk_dhe_ke, it offers these
         groups in preference order in ClientHello key_share.";
      reference
        "RFC 8446: The Transport Layer Security (TLS) Protocol
                   Version 1.3, Sections 4.2.7 and 4.2.8";
    }
  }

  augment "/sys:system/sys-tcs-plus:tacacs-plus/"
        + "sys-tcs-plus:client-credentials/"
        + "sys-tcs-plus:auth-type/"
        + "sys-tcs-plus:tls13-epsk/"
        + "sys-tcs-plus:tls13-epsk" {
    if-feature "psk-dhe-ke-hello-params";
    description
      "This augment adds configuration for PSK DHE supported groups to
       reusable client credential bundles.";
    uses psk-dhe-ke-hello-params;
  }

  augment "/sys:system/sys-tcs-plus:tacacs-plus/"
        + "sys-tcs-plus:server/"
        + "sys-tcs-plus:security/"
        + "sys-tcs-plus:tls/"
        + "sys-tcs-plus:client-identity/"
        + "sys-tcs-plus:ref-or-explicit/"
        + "sys-tcs-plus:explicit/"
        + "sys-tcs-plus:auth-type/"
        + "sys-tcs-plus:tls13-epsk/"
        + "sys-tcs-plus:tls13-epsk" {
    if-feature "psk-dhe-ke-hello-params";
    description
      "This augment adds configuration for PSK DHE supported groups to
       the TLS client identity of each TACACS+ server.";
    uses psk-dhe-ke-hello-params;
  }
}
