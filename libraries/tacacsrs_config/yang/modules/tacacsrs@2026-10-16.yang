module tacacsrs {
  yang-version 1.1;
  namespace "urn:authscaffold:tacacs-rs:yang:tacacsrs";
  prefix trs;

  import ietf-system {
    prefix sys;
    reference
      "RFC 7317: A YANG Data Model for System Management";
  }

  import ietf-system-tacacs-plus {
    prefix sys-tcs-plus;
    reference
      "RFC 9950: A YANG Data Model for Terminal Access Controller
                 Access-Control System Plus (TACACS+)";
  }

  import ietf-yang-types { prefix yang; }

  organization
    "AuthScaffold tacacs-rs project";
  contact
    "Project Web: <https://github.com/AuthScaffold/tacacs-rs>";
  description
    "Project-owned TACACS+ configuration extensions for tacacs-rs.";

  revision 2026-10-16 {
    description "Adds bounded read-only server, connection, TLS, and operation diagnostics.";
  }

  revision 2026-10-06 {
    description
      "Adds local service listeners, failover, and request-admission policy.";
  }

  revision 2026-05-20 {
    description
      "Adds TLS 1.3 PSK psk_dhe_ke supported group configuration.";
    reference
      "RFC 8446: The Transport Layer Security (TLS) Protocol
                 Version 1.3, Sections 4.2.7 and 4.2.8";
  }

  feature psk-dhe-ke-hello-params {
    description
      "Indicates that TLS 1.3 PSK psk_dhe_ke ClientHello supported
       group and key share parameters are configurable.";
  }

  typedef failover-strategy {
    type enumeration {
      enum deferred-failover {
        description
          "Record a failed attempt and let the next request select the next server.";
      }
      enum ordered-safe-retry {
        description
          "Try the next eligible server during the current request when replay is safe.";
      }
    }
    description
      "Failover behavior for a local TACACS+ service.";
  }

  typedef proxy-credential-source {
    type enumeration {
      enum unobfuscated {
        description "Require unobfuscated downstream packets.";
      }
      enum inline {
        description "Use the configured proxy shared secret.";
      }
      enum local-proxy-row {
        description
          "Use the highest-priority upstream row matching the local proxy endpoint.
           A missing row or missing secret rejects the candidate configuration.";
      }
    }
    description "Authoritative source of downstream proxy obfuscation credentials.";
  }

  grouping diagnostic-connection {
    description "Public metadata from one established connection. No credentials are included.";
    leaf connection-id { type uint64; description "Process-local connection identity."; }
    leaf peer-address { type string; description "Observed peer socket address, including its port."; }
    leaf address-family { type enumeration { enum IPv4; enum IPv6; } description "Observed peer address family."; }
    leaf established-at { type yang:date-and-time; description "Time transport establishment completed."; }
    leaf single-connect { type boolean; description "Observed first-reply single-connect agreement. Absent before observation."; }
    leaf tls-enabled { type boolean; description "Whether this established transport uses TLS."; }
    leaf tls-version { type string; description "Negotiated TLS version. Absent for cleartext connections."; }
    leaf tls-cipher { type string; description "Negotiated cipher suite, never key material."; }
    leaf fips-enabled { type boolean; description "Observed backend FIPS mode. Absent when unknown."; }
  }

  grouping diagnostic-operation {
    description "Per-server operations in local completion order, not aggregate logical retries.";
    leaf requests { type yang:counter64; description "First requests accepted for execution, including queued sends."; }
    leaf passed { type yang:counter64; description "Validated terminal success replies."; }
    leaf denied { type yang:counter64; description "Validated authentication failures or authorization denials."; }
    leaf errors { type yang:counter64; description "Other validated terminal replies."; }
    leaf consecutive-failures { type uint64; description "Consecutive terminal non-success replies; success resets this gauge."; }
  }

  augment "/sys:system/sys-tcs-plus:tacacs-plus/sys-tcs-plus:server/sys-tcs-plus:statistics" {
    description "Distinguishes successful establishments from the standard connection-open attempt counter.";
    leaf connection-successes { config false; type yang:counter64; description "Completed TCP or TLS establishments, including required TLS verification."; }
  }

  augment "/sys:system/sys-tcs-plus:tacacs-plus/sys-tcs-plus:server" {
    description "Measured server diagnostics for one captured routing generation and counter epoch.";
    container diagnostics {
      config false;
      description "Read-only endpoint telemetry. Missing observations are not represented as false or zero.";
      leaf address { type string; description "Configured host address or DNS name."; }
      leaf port { type uint16; description "Configured service port."; }
      leaf source-address { type string; description "Configured source address when present."; }
      leaf routing-instance { type string; description "Configured routing instance when present."; }
      leaf configured-single-connect { type boolean; description "Configured negotiation policy, not observed server support."; }
      leaf connection-timeout-seconds { type uint16; units "seconds"; description "Configured connection timeout."; }
      leaf state { type enumeration { enum connected; enum connecting; enum disconnected; enum not-attempted; } description "Transport state, distinct from routing eligibility and agent readiness."; }
      leaf connecting { type uint64; description "Transport attempts in progress."; }
      leaf connected { type uint64; description "Established transports not yet closed."; }
      leaf expected-replies { type uint64; description "Requests awaiting validated completion, including queued sends. Cancellation clears the gauge."; }
      leaf last-attempt { type yang:date-and-time; description "Most recent transport attempt."; }
      leaf last-success { type yang:date-and-time; description "Most recent completed transport establishment."; }
      leaf last-disconnect { type yang:date-and-time; description "Most recent established-transport close."; }
      leaf last-disconnect-reason { type enumeration { enum graceful; enum peer; enum malformed-packet; enum no-response; enum write-error; enum read-error; enum credential-expired; enum other; } description "First observed close cause; cleanup does not overwrite it."; }
      list connection { key connection-id; max-elements 32; description "Bounded active connection details."; uses diagnostic-connection; }
      leaf connections-omitted { type uint64; description "Active transports omitted from the bounded detail list."; }
      container last-connection { presence "A connection completed establishment."; description "Last established connection, which may no longer be active."; uses diagnostic-connection; }
      list routing {
        key operation;
        description "Configured operation eligibility and current circuit hold state.";
        leaf operation { type enumeration { enum authentication; enum authorization; enum accounting; } }
        leaf eligible { type boolean; }
        leaf on-hold { type boolean; }
      }
      leaf handshake-attempts { type yang:counter64; description "TLS handshake attempts."; }
      leaf handshake-successes { type yang:counter64; description "TLS handshakes with completed required verification."; }
      leaf handshake-failures { type yang:counter64; description "Failed or cancelled TLS establishment attempts."; }
      leaf read-errors { type yang:counter64; description "First observed read failures on connections."; }
      leaf write-errors { type yang:counter64; description "First observed write failures on connections."; }
      leaf receive-timeouts { type yang:counter64; description "Receive I/O timeouts and fixed-exchange deadline expirations."; }
      leaf send-timeouts { type yang:counter64; description "Observed send I/O timeouts."; }
      leaf resets { type yang:counter64; description "Established connection closes with a non-graceful cause."; }
      leaf peer-disconnects { type yang:counter64; description "Peer EOF or reset closes."; }
      leaf malformed-disconnects { type yang:counter64; description "Protocol or framing violation closes."; }
      leaf no-response-disconnects { type yang:counter64; description "Timeout-induced connection closes."; }
      leaf credential-expiry-disconnects { type yang:counter64; description "Credential lifetime closes."; }
      leaf other-disconnects { type yang:counter64; description "Other aborts, including local shutdown cancellation and I/O failures."; }
      leaf packets-since-reset-sent { type yang:counter64; description "Complete packets sent since the most recent endpoint connection reset."; }
      leaf packets-since-reset-received { type yang:counter64; description "Complete packets received since the most recent endpoint connection reset."; }
      leaf watchdog-preflights { type yang:counter64; description "Explicitly configured accounting-watchdog preflight attempts, including setup failures."; }
      leaf watchdog-successes { type yang:counter64; description "Successful accounting-watchdog preflights."; }
      leaf watchdog-failures { type yang:counter64; description "Failed or cancelled accounting-watchdog preflights."; }
      leaf watchdog-preflights-since-reset { type yang:counter64; description "Preflight attempts since the latest endpoint connection reset. No periodic timer is implied."; }
      leaf tls-read-errors { type yang:counter64; description "Read failures on TLS transports."; }
      leaf tls-write-errors { type yang:counter64; description "Write failures on TLS transports."; }
      leaf tls-certificate-errors { type yang:counter64; description "Certificate-related TLS establishment failures."; }
      leaf tls-revoked-certificates { type yang:counter64; description "Native verification failures identified as revoked certificates."; }
      leaf tls-untrusted-ca { type yang:counter64; description "Native verification failures identified as untrusted issuers."; }
      leaf tls-expired-certificates { type yang:counter64; description "Native verification failures identified as invalid certificate dates."; }
      leaf tls-protocol-mismatches { type yang:counter64; description "Native SSL reason codes identifying unsupported or mismatched protocol versions."; }
      leaf tls-cipher-mismatches { type yang:counter64; description "Native SSL reason codes identifying absent or incompatible ciphers."; }
      leaf tls-other-errors { type yang:counter64; description "Other TLS establishment errors; no classification is inferred from error text."; }
      container authentication { uses diagnostic-operation; }
      container authorization { uses diagnostic-operation; }
      container accounting { uses diagnostic-operation; }
      leaf-list unsupported { type string; description "Capabilities this runtime does not measure; these must not be displayed as zero counters."; }
    }
  }

  grouping request-limits {
    description
      "Admission and execution limits shared by all callers of one operation.";
    leaf request-timeout-seconds {
      type uint32 { range "1..max"; }
      units "seconds";
      default 30;
      description
        "Total request budget from capture before admission through completion.
         Includes admission, connection setup, retries, and proxy continuations.
         Server timeouts can shorten individual stages but cannot extend this budget.
         Reload does not change the deadline of an existing request.";
    }
    leaf max-body-length {
      type uint32 { range "1..65536"; }
      units "bytes";
      default 16384;
      description
        "Maximum encoded TACACS+ request body length.";
    }
    leaf max-concurrent-requests {
      type uint32 { range "1..max"; }
      default 64;
      description
        "Maximum concurrent requests for one operation.";
    }
  }

  augment "/sys:system/sys-tcs-plus:tacacs-plus" {
    description "Generation association for operational snapshots.";
    leaf runtime-generation {
      config false;
      type uint64;
      description "Runtime generation captured for this operational snapshot.";
    }
  }

  augment "/sys:system/sys-tcs-plus:tacacs-plus/sys-tcs-plus:server" {
    description "Counter lifetime identity independent of routing generations.";
    leaf counter-epoch {
      config false;
      type uint64;
      description
        "Process-local counter lifetime identity. Unchanged endpoints retain it
         across reloads; replaced endpoints receive a new identity and discontinuity time.";
    }
  }

  augment "/sys:system" {
    description
      "Local TACACS+ service policy, separate from the ordered upstream server list.";
    container local-services {
      description
        "Startup listener configuration. Changes require a service restart.";
      leaf max-connections {
        type uint16 { range "1..max"; }
        default 64;
        description "Maximum served connections per enabled listener.";
      }
      leaf max-client-api-streams {
        type uint16 { range "1..max"; }
        default 64;
        description "Maximum concurrent HTTP/2 streams on one client API connection.";
      }
      leaf connection-lifetime-seconds {
        type uint32 { range "1..max"; }
        units "seconds";
        default 300;
        description
          "Maximum lifetime of a served local connection, including setup and reply delivery.
           The listener closes the connection at expiry, even when requests remain active.";
      }
      must "client-api-enabled = 'true' or tacacs-proxy-enabled = 'true'";
      must "(tacacs-proxy-enabled = 'true' and tacacs-proxy-endpoint) or
            (tacacs-proxy-enabled = 'false' and not(tacacs-proxy-endpoint))";
      must "tacacs-proxy-enabled = 'true' or proxy-credential-source = 'unobfuscated'";
      must "(proxy-credential-source = 'inline' and proxy-shared-secret) or
        (proxy-credential-source != 'inline' and not(proxy-shared-secret))";
      leaf client-api-enabled {
        type boolean;
        default true;
        description
          "Enables the local client API.";
      }
      leaf client-api-endpoint {
        type string { length "1..107"; }
        default "/run/tacacs/tacacs.sock";
        description
          "Absolute Unix socket path for the client API.";
      }
      leaf tacacs-proxy-enabled {
        type boolean;
        default false;
        description
          "Enables the raw TACACS+ proxy.";
      }
      leaf tacacs-proxy-endpoint {
        type string { length "1..max"; }
        description
          "Absolute Unix socket path or numeric IP socket address for the proxy.
           IPv6 addresses use brackets. TCP port zero requests an ephemeral port.";
      }
      leaf unix-socket-mode {
        type uint16 { range "0..511"; }
        default 432;
        description
          "Unix socket permission bits as a decimal integer. The default is octal 660.";
      }
      leaf proxy-credential-source {
        type proxy-credential-source;
        default unobfuscated;
        description "Selects downstream credentials independently of loop prevention.";
      }
      leaf proxy-shared-secret {
        type string { length "1..max"; }
        description "Downstream shared secret for the inline credential source.";
      }
    }
    container runtime-policy {
      description
        "Failover and admission controls for local client API and proxy services.";
      leaf shutdown-timeout-seconds {
        type uint32 { range "1..max"; }
        units "seconds";
        default 30;
        description
          "Graceful shutdown budget for runtime and host cleanup.
           The host captures one deadline when shutdown starts.
           At expiry, pending asynchronous work is cancelled.
           Policy updates do not extend a shutdown already in progress.";
      }
      leaf credential-stale-timeout-seconds {
        type uint32 { range "1..max"; }
        units "seconds";
        default 300;
        description
          "Grace interval for referenced credentials after invalidation or provider loss.
           Retries and policy changes do not renew the interval.
           At expiry, withdraw upstreams until complete credential revalidation succeeds.";
      }
         leaf credential-refresh-interval-seconds {
           type uint32 { range "1..max"; }
           units "seconds";
           default 60;
           description
          "Maximum scheduled delay between provider credential refresh attempts.
           Start earlier when prepared material approaches expiry.
           Refresh does not extend signed or provider validity and does not
           mark valid material stale unless revalidation fails.";
         }
      leaf source-stale-timeout-seconds {
        type uint32 { range "1..max"; }
        units "seconds";
        default 300;
        description
          "Maximum grace interval after applied source configuration becomes stale.
           Capture the deadline at the first observed source failure or rejection.
           Retries, credential refresh, and policy changes do not renew the interval.
           At expiry, withdraw upstreams until a valid source is applied again.";
      }
      leaf failover-recovery-interval-seconds {
        type uint32 { range "1..max"; }
        units "seconds";
        default 30;
        description
          "Interval before a failed route receives one recovery trial.";
      }
      leaf client-api-failover-strategy {
        type failover-strategy;
        default deferred-failover;
        description
          "Failover policy for requests received through the local client API.";
      }
      leaf tacacs-proxy-failover-strategy {
        type failover-strategy;
        default deferred-failover;
        description
          "Failover policy for initial requests received through the TACACS+ proxy.";
      }
      container authentication {
        description
          "Shared authentication admission limits.";
        uses request-limits {
          refine max-body-length { default 4096; }
        }
      }
      container authorization {
        description
          "Shared authorization admission limits.";
        uses request-limits;
      }
      container accounting {
        description
          "Shared accounting admission limits.";
        uses request-limits;
      }
    }
  }

  typedef psk-dhe-ke-supported-group {
    type enumeration {
      enum x25519 {
        description
          "X25519 elliptic curve group.";
        reference
          "RFC 8446: The Transport Layer Security (TLS) Protocol
                     Version 1.3, Section 4.2.7";
      }
      enum secp256r1 {
        description
          "NIST P-256 elliptic curve group.";
      }
      enum secp384r1 {
        description
          "NIST P-384 elliptic curve group.";
      }
      enum secp521r1 {
        description
          "NIST P-521 elliptic curve group.";
      }
      enum ffdhe2048 {
        description
          "Finite field Diffie-Hellman group ffdhe2048.";
        reference
          "RFC 7919: Negotiated Finite Field Diffie-Hellman Ephemeral
                     Parameters for TLS";
      }
      enum ffdhe3072 {
        description
          "Finite field Diffie-Hellman group ffdhe3072.";
      }
      enum ffdhe4096 {
        description
          "Finite field Diffie-Hellman group ffdhe4096.";
      }
      enum ffdhe6144 {
        description
          "Finite field Diffie-Hellman group ffdhe6144.";
      }
      enum ffdhe8192 {
        description
          "Finite field Diffie-Hellman group ffdhe8192.";
      }
    }
    description
      "TLS 1.3 supported groups that tacacs-rs may use for
       psk_dhe_ke ClientHello key share generation.";
    reference
      "RFC 8446: The Transport Layer Security (TLS) Protocol
                 Version 1.3, Section 4.2.7";
  }

  grouping psk-dhe-ke-hello-params {
    description
      "Configuration for TLS 1.3 PSK psk_dhe_ke ClientHello
       supported group and key share parameters.";

    leaf-list psk-dhe-ke-groups {
      if-feature "psk-dhe-ke-hello-params";
      type psk-dhe-ke-supported-group;
      ordered-by user;
      description
        "Supported groups to offer, in preference order, in
         ClientHello key_share when using TLS 1.3 PSK psk_dhe_ke.";
      reference
        "RFC 8446: The Transport Layer Security (TLS) Protocol
                   Version 1.3, Sections 4.2.7 and 4.2.8";
    }
  }

  grouping client-certificate-chain {
    description
      "Intermediate certificates for a configured TLS client identity.";
    leaf-list intermediate-certificate {
      type binary {
        length "1..max";
      }
      ordered-by user;
      description
        "DER-encoded intermediate certificates in issuer order, starting
         with the issuer of cert-data. Each entry contains one X.509
         certificate. Do not include the leaf or a self-signed root.";
    }
  }

  grouping certificate-revocation-policy {
    description
      "Required revocation evidence for certificate TLS peer authentication.";
    container require-crls {
      presence "Require fresh CRLs for certificate TLS server authentication.";
      description
        "Require complete CRL evidence for the verified server certificate path.
         An unpartitioned base can advertise one explicitly supplied delta.
         Both lists must be fresh and match issuer, scope, and authority key
         identifier. CRL numbers must identify a compatible increasing update.
         Direct CRLs can restrict certificate type and distribution-point scope.
         Multiple scopes for one issuer must cover disjoint certificate types.
         Within each scope, reason partitions must be disjoint.
         At most 128 lists and 4 MiB are accepted.
         Native verification requires complete reason and path coverage.
         Exact peer pins and PSK authentication are not supported in this mode.
         Unavailable, invalid, stale, or incomplete evidence fails closed.";
      leaf max-age-seconds {
        type uint32 { range "1..max"; }
        default 300;
        description
          "Maximum seconds since each CRL thisUpdate. The earlier of this
           limit and nextUpdate bounds evidence use without stale grace.";
      }
      choice evidence {
        mandatory true;
        case inline {
          leaf-list crl {
            type binary { length "1..max"; }
            min-elements 1;
            description "One full or delta DER CRL per entry.";
          }
        }
        case provider {
          leaf evidence-reference {
            type string { length "1..max"; }
            mandatory true;
            description "Opaque provider reference to a complete CRL set.";
          }
        }
      }
    }
    container require-ocsp {
      presence "Require independently supplied OCSP evidence for the peer leaf.";
      description
        "Requires a fetched or inline response independently of any mandatory staple.
         The actual peer, signer, status, and signed freshness are verified before client authentication.";
      leaf max-response-age-seconds {
        type uint32 { range "1..max"; }
        default 300;
      }
      choice evidence {
        mandatory true;
        case inline {
          leaf response { type binary { length "1..65536"; } mandatory true; }
        }
        case provider {
          leaf evidence-reference { type string { length "1..max"; } mandatory true; }
        }
      }
    }
    container require-stapled-ocsp {
      presence "Require fresh authenticated OCSP evidence for the peer leaf.";
      description
        "Request a stapled OCSP response and fail closed if evidence is
         unavailable, invalid, stale, unknown, or revoked. Responses must
         be signed by the issuer or a responder issued directly by it.
         Delegated responders require OCSP signing usage and either a valid
         noncritical No Check extension or verified configured CRL evidence.
         This requirement can be combined with require-crls. Both checks
         must pass. OCSP covers the peer leaf; CRLs cover the CA path.";
      leaf max-response-age-seconds {
        type uint32 { range "1..max"; }
        default 300;
        description
          "Maximum time since thisUpdate. Evidence expires at the earlier
           of this limit and nextUpdate, when nextUpdate is present.
           No clock-skew allowance or stale grace extends this interval.";
      }
    }
  }

  augment "/sys:system/sys-tcs-plus:tacacs-plus/"
        + "sys-tcs-plus:server-credentials" {
    description
      "Adds required stapled OCSP to reusable server authentication.";
    uses certificate-revocation-policy;
  }

  augment "/sys:system/sys-tcs-plus:tacacs-plus/"
        + "sys-tcs-plus:server/"
        + "sys-tcs-plus:security/"
        + "sys-tcs-plus:tls/"
        + "sys-tcs-plus:server-authentication/"
        + "sys-tcs-plus:ref-or-explicit/"
        + "sys-tcs-plus:explicit" {
    description
      "Adds required stapled OCSP to per-server certificate authentication.";
    uses certificate-revocation-policy;
  }

  augment "/sys:system/sys-tcs-plus:tacacs-plus/"
        + "sys-tcs-plus:client-credentials/"
        + "sys-tcs-plus:auth-type/"
        + "sys-tcs-plus:certificate/"
        + "sys-tcs-plus:certificate/"
        + "sys-tcs-plus:inline-or-keystore/"
        + "sys-tcs-plus:inline/"
        + "sys-tcs-plus:inline-definition" {
    description
      "Adds a client certificate chain to reusable inline credentials.";
    uses client-certificate-chain;
  }

  augment "/sys:system/sys-tcs-plus:tacacs-plus/"
        + "sys-tcs-plus:server/"
        + "sys-tcs-plus:security/"
        + "sys-tcs-plus:tls/"
        + "sys-tcs-plus:client-identity/"
        + "sys-tcs-plus:ref-or-explicit/"
        + "sys-tcs-plus:explicit/"
        + "sys-tcs-plus:auth-type/"
        + "sys-tcs-plus:certificate/"
        + "sys-tcs-plus:certificate/"
        + "sys-tcs-plus:inline-or-keystore/"
        + "sys-tcs-plus:inline/"
        + "sys-tcs-plus:inline-definition" {
    description
      "Adds a client certificate chain to per-server inline credentials.";
    uses client-certificate-chain;
  }

  augment "/sys:system/sys-tcs-plus:tacacs-plus/"
        + "sys-tcs-plus:client-credentials/"
        + "sys-tcs-plus:auth-type/"
        + "sys-tcs-plus:tls13-epsk/"
        + "sys-tcs-plus:tls13-epsk" {
    if-feature "psk-dhe-ke-hello-params";
    description
      "Adds PSK DHE supported group configuration to reusable client
       credential bundles.";
    uses psk-dhe-ke-hello-params;
  }

  augment "/sys:system/sys-tcs-plus:tacacs-plus/"
        + "sys-tcs-plus:server/"
        + "sys-tcs-plus:security/"
        + "sys-tcs-plus:tls/"
        + "sys-tcs-plus:client-identity/"
        + "sys-tcs-plus:ref-or-explicit/"
        + "sys-tcs-plus:explicit/"
        + "sys-tcs-plus:auth-type/"
        + "sys-tcs-plus:tls13-epsk/"
        + "sys-tcs-plus:tls13-epsk" {
    if-feature "psk-dhe-ke-hello-params";
    description
      "Adds PSK DHE supported group configuration to per-server TLS
       client identities.";
    uses psk-dhe-ke-hello-params;
  }
}
